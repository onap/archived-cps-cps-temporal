#
# ============LICENSE_START=======================================================
# Copyright (C) 2021 Bell Canada.
# ================================================================================
# Licensed under the Apache License, Version 2.0 (the "License");
# you may not use this file except in compliance with the License.
# You may obtain a copy of the License at
#
#       http://www.apache.org/licenses/LICENSE-2.0
#
# Unless required by applicable law or agreed to in writing, software
# distributed under the License is distributed on an "AS IS" BASIS,
# WITHOUT WARRANTIES OR CONDITIONS OF ANY KIND, either express or implied.
# See the License for the specific language governing permissions and
# limitations under the License.
#
# SPDX-License-Identifier: Apache-2.0
# ============LICENSE_END=========================================================

module test-tree {
    yang-version 1.1;

    namespace "org:onap:cps:test:test-tree";
    prefix tree;
    revision "2020-02-02";

    container test-tree {
        list branch {
            key "name";
            leaf name {
                type string;
            }
            container nest {
                leaf name {
                    type string;
                }
                leaf-list birds {
                    type string;
                }
            }
        }
    }
}
